ASUSTOR-UPS-MIB DEFINITIONS ::= BEGIN

IMPORTS
	OBJECT-GROUP, MODULE-COMPLIANCE
				FROM SNMPv2-CONF
	enterprises, MODULE-IDENTITY, OBJECT-TYPE, Integer32
				FROM SNMPv2-SMI;
				
asustor	 OBJECT IDENTIFIER 
	::= { enterprises 44738 }
	
asustorUps MODULE-IDENTITY
    LAST-UPDATED "202401010000Z"
    ORGANIZATION "www.asustor.com"
    CONTACT-INFO
         "postal: ASUSTOR Inc.
		 email: support@asustor.com"
    DESCRIPTION
        "Characteristics of the ups information"
    REVISION "202401010000Z"
    DESCRIPTION "Initial revision"
    ::= { asustor 6 }

SeqStructUps ::= SEQUENCE {
	upsIndex					Integer32,
    upsManufacture				OCTET STRING,
	upsModel					OCTET STRING,
	upsVendorId					OCTET STRING,
	upsProductId				OCTET STRING,
	upsInputSensitivity			OCTET STRING,
	upsStatus					OCTET STRING,
	upsBatteryRemainSecond		Integer32,
	upsBatteryChargePercent 	Integer32,
	upsBatteryChargeLowPercent 	Integer32,
	upsInputVoltage				Integer32
}

upsTable OBJECT-TYPE
    SYNTAX	   	SEQUENCE OF SeqStructUps
    MAX-ACCESS	not-accessible
    STATUS	   	current
    DESCRIPTION
    "Asustor ups table"
    ::= { asustorUps 1 }

upsEntry OBJECT-TYPE
    SYNTAX		SeqStructUps
    MAX-ACCESS	not-accessible
    STATUS	   	current
    DESCRIPTION
    "For all ups entry"
    INDEX   { upsIndex }
    ::= { upsTable 1 }

upsIndex OBJECT-TYPE
    SYNTAX	   	Integer32
    MAX-ACCESS	not-accessible
    STATUS	   	current
    DESCRIPTION
    "The index of ups table"
    ::= { upsEntry 1 }

upsManufacture OBJECT-TYPE
    SYNTAX	  	OCTET STRING
    MAX-ACCESS  read-only
    STATUS	  	current
    DESCRIPTION
    "The ups bay"
    ::= { upsEntry 2 }

upsModel OBJECT-TYPE
    SYNTAX	  	OCTET STRING
    MAX-ACCESS	read-only
    STATUS	  	current
    DESCRIPTION
    "The ups model name"
    ::= { upsEntry 3 }

upsVendorId OBJECT-TYPE
    SYNTAX	  	OCTET STRING
    MAX-ACCESS	read-only
    STATUS	  	current
    DESCRIPTION
    "The ups vendor id"
    ::= { upsEntry 4 }

upsProductId OBJECT-TYPE
    SYNTAX	  	OCTET STRING
    MAX-ACCESS  read-only
    STATUS	  	current
    DESCRIPTION
    "The ups product id"
    ::= { upsEntry 5 }
    
upsInputSensitivity OBJECT-TYPE
    SYNTAX	  	OCTET STRING
    MAX-ACCESS  read-only
    STATUS	  	current
    DESCRIPTION
    "The ups input sensitivity"
    ::= { upsEntry 6 }
    
upsStatus OBJECT-TYPE
    SYNTAX	  	OCTET STRING
    MAX-ACCESS  read-only
    STATUS	  	current
    DESCRIPTION
    "The ups status"
    ::= { upsEntry 7 }

upsBatteryRemainSecond OBJECT-TYPE
    SYNTAX	   	Integer32
    MAX-ACCESS	read-only
    STATUS	   	current
    DESCRIPTION
    "The ups battery remain in second"
    ::= { upsEntry 8 }

upsBatteryChargePercent OBJECT-TYPE
    SYNTAX	  	Integer32
    MAX-ACCESS  read-only
    STATUS	  	current
    DESCRIPTION
    "The ups battery charge percent"
    ::= { upsEntry 9 }

upsBatteryChargeLowPercent OBJECT-TYPE
    SYNTAX	  	Integer32
    MAX-ACCESS  read-only
    STATUS	  	current
    DESCRIPTION
    "The ups battery charge low percent"
    ::= { upsEntry 10 }

upsInputVoltage OBJECT-TYPE
    SYNTAX	  	Integer32
    MAX-ACCESS  read-only
    STATUS	  	current
    DESCRIPTION
    "The ups input voltage"
    ::= { upsEntry 11 }

upsConformances OBJECT IDENTIFIER ::= { asustorUps 2 }
upsCompliances 	OBJECT IDENTIFIER ::= { upsConformances 1 }
upsGroups		OBJECT IDENTIFIER ::= { upsConformances 2 }

upsCompliance MODULE-COMPLIANCE
    STATUS  current
    DESCRIPTION
        "The compliance force implement the ASUSTOR UPS MIB."
    MODULE
        MANDATORY-GROUPS { upsGroup }
    ::= { upsCompliances 1 }

upsGroup OBJECT-GROUP
	OBJECTS { upsManufacture,
			  upsModel,
			  upsVendorId,
	   		  upsProductId,
	   		  upsInputSensitivity,
	   		  upsStatus,
	   		  upsBatteryRemainSecond,
	   		  upsBatteryChargePercent,
	   		  upsBatteryChargeLowPercent,
	   		  upsInputVoltage }
    STATUS  current
    DESCRIPTION
        "A collection of objects providing basic information of an asustor ups entity."
    ::= { upsGroups 1 }

END
